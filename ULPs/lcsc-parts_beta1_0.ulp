#usage "<b>Search LCSC's database of free CAD symbols and footprints</b><p>\n"
"Version: 0.1 - The SnapEDA CadSoft Eagle ULP - 10-21-15<br/>"
"<author>Author: SnapEDA, Inc. (info@snapeda.com). Visit http://www.snapeda.com to learn more.</author>"
#require 5.1000
#include "json.inc"
string version = "2.3";  //ulp version

// SnapEDA API Response Variables
int SnapEDAHits; // Hits returned by SnapEDA
int SnapEDAVisible; // # of products visible
string SnapEDAResult; // JSON response from SnapEDA API

// SnapEDA API - CAD Part Attributes
string compImage[]; // Image of symbol
string fpImage[]; // Image of footprint
string imageSets; // all CAD file images
string Image[]; // array of Image files

// SnapEDA API - UniPart Attributes
string mpn[]; // Manufacturer part number
string manufacturer[]; // Manufacturer name
string description[]; // Description of MPN
string manLogo[];
string availability[] ; // Availability of this mpn at distributors
string compstatus; //  Availability of CAD component(s) on SnapEDA
string fpstatus;   // Availability of footprint(s) on SnapEDA
string dsstatus; //  Availability of datasheet on SnapEDA
string mpnImage[]; // Image of mpn
string snapURL; // Url of UniPart product page on SnapEDA
string avgPrice[]; // Average price across distributors (replace w/ PF price)
string snaplink[]; // Link to SnapEDA part page
string UniPackage[]; // Package used by UniPart

// Initialiaztion of GUI Elements
string TableHeader = ("Manufacturer\tPart Number\tAvailability\tPackage\tSymbol\tFootprint\tDatasheet\tAvg. Price (USD)");
string compicon = "No"; // Link to symbol icon
string fpicon = "No"; // Link to footprint icon
string dsicon = "No"; // Link to datasheet icon
string SnapEDALogo;
string SearchQuery = "Search for a part number, keyword, or manufacturer. Examples: esp8266ex or Voltage Regulator";
string HTMLPane = "";
int search=0; // Flag that is 1 if in search mode

// Page
int CurrentPage=1;
int pagecount;
string pageLink;
string Pages[];

// History Tracking
string SearchHist[]; // History of search entries

// Processed Data
string Products[]; // Array of results returned from SnapEDA
int    ProductCount; // # of downloaded products
int    ProductCountInList;
numeric string ProductList[]; // Products converted to a list for displaying (part of information)

// User-defined variables
string query;

// Variables for display
int    ProductCountPerPage = 25;
string ExtraInfo = ""; // Extra information to user in certain cases

// TD
int    ProductOffset; // Product offset
int    Offset; // Offset in query

//Convert Int to String
string I2Str(int i) {
   string str;
   sprintf(str, "%d", i);
   return str;
}

// SnapEDA API url
string GetSnapEDAURL(int CurrentPage)
{
 
//  https://lcsc.com/search?q=esp8266ex

//  return "http://www.snapeda.com/api/v1/parts/search?q=" + SearchQuery + "&format=eagle&page=" + I2Str(CurrentPage);
  return "https://lcsc.com/search?q=" + SearchQuery + "&format=eagle&page=" + I2Str(CurrentPage);

}

string PageCountInfo="";                      // Info on search results
int    Productsel = -1;              // Product currently selected

// Dialog logics
int    DIMode = 1;                     // to redisplay dialog

// JSON library variables //
string strResult;
string key;
string chrrep(string str,char a,char b){
  for(int i = 0;i<strlen(str);i++){
    if(str[i]==a){
      str[i] = b;
    }
  }
  return(str);
}

// Get the mpn data
void RefreshVariables(int prIdx) {
      // Parse out key attributes and parse out quotes
      strsplit(manufacturer, (json_GetKeyItem(Products[prIdx],"manufacturer")), '"');
      strsplit(availability, (json_GetKeyItem(Products[prIdx],"availability")), '"');
      strsplit(mpn, (json_GetKeyItem(Products[prIdx],"name")), '"');
      strsplit(avgPrice, (json_GetKeyItem(Products[prIdx],"average_price")), '"');
      strsplit(manLogo, (json_GetKeyItem(Products[prIdx],"organization_image_100_20")), '"');
      strsplit(manLogo, manLogo[1], '?'); // splitting to remove signature
      strsplit(description, (json_GetKeyItem(Products[prIdx],"short_description")), '"');
      strsplit(UniPackage, (json_GetKeyItem(Products[prIdx],"package")), '"');
      strsplit(mpnImage, (json_GetKeyItem(Products[prIdx],"coverart")), '"');
      strsplit(mpnImage, mpnImage[3], '?');
      imageSets = json_GetKeyItem(Products[prIdx],"models");
      int cadparts = json_GetArrayCount(imageSets);
      // Store results in array
      compImage[0] = "";// ***
      fpImage[0] = ""; //***
      if (!UniPackage[3]){
      UniPackage[3] ="N/A";
      }

      if (cadparts > 0){
        int x = 0;
        for (x = 0; x < cadparts; ++x) {
         // Store the results for the particular imageSet
          string images = json_GetArrayItem(imageSets,x);
          Image[x] = images;
         }
      fpImage[0] = json_GetKeyItem(Image[0],"package_medium");
      strsplit (fpImage, (json_GetKeyItem(fpImage[0], "url")), '"');
      strsplit (fpImage, fpImage[1], '?');
      compImage[0] = json_GetKeyItem(Image[0],"symbol_medium");
      strsplit (compImage, (json_GetKeyItem(compImage[0], "url")), '"');
      strsplit (compImage, compImage[1], '?');
        }
      // Parse our the href url
      snaplink[0] = json_GetKeyItem(Products[prIdx],"_links");
      snaplink[0]= json_GetKeyItem(snaplink[0],"self");
      snaplink[0]= json_GetKeyItem(snaplink[0],"href");
      strsplit(snaplink, snaplink[0], '"');

      // Replace status with more generic term
      if (availability[1]=="Bad"){
        availability[1] = "Low";
      }
      if (availability[1]=="Warning"){
        availability[1] ="Low";
      }

      // Format the price string
      if (avgPrice[1] != "N/A"){
        strsplit(avgPrice, avgPrice[1], ' '); // Parse out the USD text
        avgPrice[1] = "$"   + avgPrice[1];
      }
      // Parse and format status of CAD part, footprint, and datasheet
      compstatus = json_GetKeyItem(Products[prIdx],"has_symbol");
      fpstatus = json_GetKeyItem(Products[prIdx],"has_footprint");
      dsstatus = json_GetKeyItem(Products[prIdx],"has_datasheet");}

// Converts the API results into a list to display in the table
void CovertToList(void)
{
   if (SnapEDAHits > (CurrentPage)*ProductCountPerPage) {
      ProductCountInList = ProductCountPerPage;
   }
   else{
   ProductCountInList = SnapEDAHits - (pagecount-1)*ProductCountPerPage;
   }
   string msg;
   ProductList[ProductCountInList] = "";
   for (int i = ProductCountInList; --i >= 0; ) {
      int prIdx = ProductOffset + i;
      RefreshVariables (prIdx);
      if (compstatus == "true") {
      compicon = "Yes";
      fpicon = "Yes";}
      else{
        compicon="No";
        if (fpstatus == "true") {
          fpicon = "Yes";}
        else{
          fpicon="No";}
        }
        if (dsstatus == "true") {
          dsicon = "Yes";}
        else{
          dsicon = "No";
      }


      ProductList[i] =
          manufacturer[1] + "\t"
        + mpn[1]+ "\t"
        + availability[1] + "\t"
        + UniPackage [3] + "\t"
        + compicon + "\t"
        + fpicon + "\t"
        + dsicon + "\t"
        + avgPrice[1] + "\t"
;
   }



  if (pagecount > 0)
     sprintf(PageCountInfo, "Page %d of %d", CurrentPage, pagecount);
   Productsel = -2; // the first item after sort
  }
void Clear(void)
{
  ProductCount = SnapEDAHits = SnapEDAVisible = ProductOffset = Offset = 0;
  ProductList[0] = "";
  Productsel = -1;
}

string WelcomePage (){
     string landingpage;
     SnapEDALogo  = "https://snapeda-static.s3.amazonaws.com/images/logo_small_55.7ee9c73a0d4f.png";
     landingpage = "https://lcsc.com/";
     if( netget( landingpage, landingpage) >= 0 ){
          return landingpage; }
     else {
          // Failed to connect to server
          return "Problem connecting to SnapEDA. Check your internet connection.";
          }
  }
// Preview window to show part content
void ShowSelection(void)
{
  if (!ProductCount) {
     Clear ();
     HTMLPane = ("No results found") + "<p>\n";
     ExtraInfo = "Please review your query, or try searching for a more general term.";
     HTMLPane += ExtraInfo;
     return;
     }
  if (Productsel < 0){
     return;
     }
  string p = Products[ProductOffset + Productsel];
  if (p) {
     RefreshVariables(ProductOffset + Productsel);

     HTMLPane = "<style type=\"text/css\" font-family=\"Open Sans\">\n"
              " .tableblock {\n"
              "     background-color: #FF761A;\n"
              " }\n"
              " .tabledata {\n"
              "     background-color: #F0F0F0;\n"
              "     padding: 2;\n"
              " }\n"
              "</style>\n"
              ;

     HTMLPane += "<table><tr><td style=\"background:#304e70;color:white;font:26px;padding:10%;\" width=\"100%\">" + mpn[1] + "<img src=\"https://s3.amazonaws.com/snapeda/ulp/snapeda.png\" style=\"float:right;\"></span></td></tr></table>\n"
                "<table cellspacing=\"3\">\n"
                "<tr><td width=\"30%\">\n";
     HTMLPane += "<img src=\"" + manLogo[0] + "\" style=\"float:left;padding=top:20px;\">"  "</div>";
     // is it possible to check for unfound image?
     if (mpnImage[0] && mpnImage[0]!="https://snapeda.s3.amazonaws.com/partpics/placeholder.jpg"){
        HTMLPane +=
              "<br><br><br><div style=\"float:left;\"> <img height=\"100\" src=\"" + mpnImage[0] + "\"></div>\n";
              }
     HTMLPane +=  "  </td>\n"
              "  <td style=\"font:18px;padding:5%;\" width=\"50%\">\n";
     if (description[1] != "N/A"){
        HTMLPane +=
              "   <p>" + description[1] + "</p>\n";
              }
    HTMLPane +=
              "   <p style=\"font:14px;\"><strong>Availability: </strong>"  + availability[1] + "<br>\n"
              "   <strong>Average Price:</strong>  "  + avgPrice[1] + "<br>\n"
              "   <strong>Package Type:</strong>  "  + UniPackage[3] + "<br></p>\n"
              "  </td><br>\n";
     if (compImage[0]){
         HTMLPane +=
                  "   <br> "
                  "   <img src=\"" + compImage[0] + "\" + height =\"150\" width=\"150\" style=\"border:15px solid #66CC33;\"> \n"
                            " \n";}
     if (fpImage[0]) {
        HTMLPane +=
                      "<img src=\"" + fpImage[0] + "\" + height =\"150\" width=\"150\">\n"
                      " \n";}
     HTMLPane +=
              "      <td style=\"font:18px;padding:40%;background:#e1e1e1;\"  width=\"20%\">\n";
      if (compstatus == "true"){
      HTMLPane +=
                "<table cellpadding=\"3\"><tr><td width=\"70%\">Symbol</td><td><img width=\"20\" src =\"https://s3.amazonaws.com/snapeda/ulp/Available.png\"></td></tr>\n";}
      else{
       HTMLPane +=
                "<table cellpadding=\"3\"><tr><td width=\"70%\">Symbol</td><td><img width=\"20\" src =\"https://s3.amazonaws.com/snapeda/ulp/Unavailable.png\"></td></tr>\n";}
      if (fpstatus == "true"){
      HTMLPane +=
                "<tr><td><span width=\"70%\">Footprint</span></td><td><img width=\"20\" src =\"https://s3.amazonaws.com/snapeda/ulp/Available.png\"></td></tr>\n";}
      else{
       HTMLPane +=
               "<tr><td>Footprint</td><td><img width=\"20\" src =\"https://s3.amazonaws.com/snapeda/ulp/Unavailable.png\"></td></tr>\n";}
      if (dsstatus == "true"){
      HTMLPane +=
                "<tr><td><span width=\"70%\">Datasheet</span></td><td><img width=\"20\" src =\"https://s3.amazonaws.com/snapeda/ulp/Available.png\"></td></tr></table><br>\n";}
      else{
       HTMLPane +=
               "<tr><td>Datasheet</td><td><img width=\"20\" src =\"https://s3.amazonaws.com/snapeda/ulp/Unavailable.png\"></td></tr></table><br>\n";}

      HTMLPane +=
                "<br><center><a href=\"http://www.snapeda.com" + snaplink[1] + "?ref=eagle" + "\">" + "Download on SnapEDA</a></center>"
                "      </td>\n"
                "    </tr></table>\n";

       HTMLPane +=  "</tr></table>\n";

  }
}

string Learnmore_url = "http://www.snapeda.com";
string Contactus_url = "mailto:info@snapeda.com";


int Search(string key, int CurrentPage)
{
   if (!DIMode) dlgRedisplay(); // Omit Redisplay if we are not really in a dialog context !
   // Get info from API
   int SnapEDAQuery = netget(SnapEDAResult, GetSnapEDAURL(CurrentPage));
   // Parse result --> get the keys
   strResult = chrrep(json_GetKeyList(SnapEDAResult),'\t','\n');
   // Get page info if CurrentPage = 0
    if (CurrentPage == 1) {
    string pages;
    int i;
    string pageLink;
    pages = json_GetKeyItem(SnapEDAResult,"pages");
    pagecount = json_GetArrayCount(pages);
    // Store pages result in array
    int page = 0;
    for (page = 0; page < pagecount ; ++page) {
       // Store the results for the particular page
      pageLink = json_GetArrayItem(pages,page);
      Pages[page] = pageLink;}
      }
    return 1;
}

int FilteredSearch(string key, int CurrentPage)
{
   Clear();
   search = 1;
   int nrUnfiltProducts;
   string results;
   int nrProductsTarget;
   int ret = 1;

   nrProductsTarget = ProductOffset + ProductCountPerPage;

   if (nrProductsTarget < ProductCount){
   return 1;}

   if (CurrentPage == 1 || CurrentPage <= pagecount) {
      // Executing the search
      ret = Search(key, CurrentPage);
      SnapEDAHits = strtol(json_GetKeyItem(SnapEDAResult,"hits"));
      SnapEDAVisible = min(25, SnapEDAHits);
      nrUnfiltProducts = SnapEDAHits;
      string results_cleaned;
      results = json_GetKeyItem(SnapEDAResult,"results");
      results_cleaned = json_GetArrayItem(results,0);

      // Store results in array
      int i = 0;
      for (i = 0; i < SnapEDAVisible; ++i) {
         // Store the results for the particular mpn
         strResult = json_GetArrayItem(results,i);
         Products[ProductCount++] = strResult;
         }
      //Offset += ProductCountPerPage;
   }
   return ret;
}

// Search
void DoSearch(string query, int CurrentPage)
{
  Clear();
  if (FilteredSearch(query, CurrentPage)) {
     CovertToList();
     ShowSelection();
  }
}

string GetSearchQuery() {
     //return form value
     return SearchQuery;
}  //end func



int IsWindows() {
  //Returns 1, if EAGLE Is running under Windows (0 for Linux/Mac)
  if ((strsub(argv[0], 0, 1) == "/") && (strsub(argv[0], 0, 2) != "//"))
    return 0;

  return 1;
}  //end sub

int IsMac(){
  if( (strsub( OS_SIGNATURE, 0, 3 ) == "Mac") ||  (strsub( OS_SIGNATURE, 0, 3 ) == "MAC") )
    return 1;

  return 0;}

void LaunchBrowser( string url ){
  string launchCmd = "";
  if( IsWindows() ){
    launchCmd = "explorer \"" + url + "\"";
    }
  else if( IsMac() ){
    launchCmd = "open " + url;
    }
  else{
    //assume all others linux
    //if you are on linux then change this line if the buttons dont work
    launchCmd = "xdg-open " + url;
    }

  //run system command
  system( launchCmd );
  }  //end launch browser


//-----------------------------------------------------------------------------
// Main ULP Code
//-----------------------------------------------------------------------------

// Initialize welcome screen
string content = WelcomePage ();

HTMLPane = "<font size=\"4\"> \
       <table width=\100%\"  style=\"font-family:Open Sans;\" align=center> \
       <tr> \
      <td width=\"100%\" style=\"padding-bottom:20px;font:36px;\"> \
       <center><a href=\"http://www.snapeda.com\"><img src=\"" + SnapEDALogo + "\"></a></center><center>The Electronics CAD Hub</center></td>\
       </tr>"
       + content +
       "</table> \
       </font>";

// Name of the window
int mainDlgResult = dlgDialog( "Search For Symbols and Footprints. Powered by SnapEDA." ) {
//main layout
dlgVBoxLayout {
  dlgHBoxLayout dlgSpacing(600);
  dlgHBoxLayout {
  dlgTextView(HTMLPane);
  dlgVBoxLayout dlgSpacing( 350 );
  }
  dlgVBoxLayout {
 dlgHBoxLayout dlgSpacing(800);
 dlgListView(TableHeader, ProductList, Productsel)
    if (dlgSelectionChanged()) {
       ShowSelection();
    }
}
dlgHBoxLayout {
       dlgStringEdit( SearchQuery );
       dlgPushButton("+Search"){
        CurrentPage=1;
        DoSearch(SearchQuery, CurrentPage);}

    dlgPushButton("<"){
       if (CurrentPage > 1) {
          CurrentPage--;
          DoSearch(query, CurrentPage);}
      else{
       dlgMessageBox("No prior pages to display.");
             }
          }
    dlgLabel(PageCountInfo, 1);
    dlgPushButton(">"){
       if (CurrentPage < pagecount) {
          CurrentPage++;
          DoSearch(query, CurrentPage);}
       else{
       dlgMessageBox("No additional pages to display.");
       }
          }

}  //end box layout

//buttons to submit and exit
dlgHBoxLayout{
dlgPushButton( "Send Feedback" ) LaunchBrowser("mailto:info@snapeda.com" );
dlgHBoxLayout dlgSpacing(610);
     dlgPushButton( "Close" ) dlgReject();
}  //end box layout
}  //end v box layout]
};  //end mainDlgResult
// What does this part of the code do?
void SaveCfg(void) {
   cfgset("ULP:designlink.SearchHistory", strjoin(SearchHist, '\t'));
   //SaveCfg();
}
